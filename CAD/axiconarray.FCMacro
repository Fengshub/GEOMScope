# FreeCAD MACRO script for placing objects as array
doc = FreeCAD.newDocument()
cylinder = doc.addObject("Part::Cone","Cone")
cylinder.Radius1=0.15
cylinder.Radius2=0
cylinder.Height=0.005
doc.recompute()
#obj=doc.copyObject(sphere)
cylinder.Placement.Base=FreeCAD.Vector(-0.59,-0.59,0)
obj=doc.copyObject(cylinder)
obj.Placement.Base=FreeCAD.Vector(-0.31,-0.7,0)
obj=doc.copyObject(cylinder)
obj.Placement.Base=FreeCAD.Vector(-0.24,-0.43,0)
obj=doc.copyObject(cylinder)
obj.Placement.Base=FreeCAD.Vector(0.03,-0.67,0)
obj=doc.copyObject(cylinder)
obj.Placement.Base=FreeCAD.Vector(-0.54,-0.27,0)
obj=doc.copyObject(cylinder)
obj.Placement.Base=FreeCAD.Vector(-0.57,0.02,0)
obj=doc.copyObject(cylinder)
obj.Placement.Base=FreeCAD.Vector(0.29,-0.5,0)
obj=doc.copyObject(cylinder)
obj.Placement.Base=FreeCAD.Vector(-0.46,0.3,0)
obj=doc.copyObject(cylinder)
obj.Placement.Base=FreeCAD.Vector(-0.16,0.52,0)
obj=doc.copyObject(cylinder)
obj.Placement.Base=FreeCAD.Vector(0.14,0.35,0)
obj=doc.copyObject(cylinder)
obj.Placement.Base=FreeCAD.Vector(0.55,-0.57,0)
obj=doc.copyObject(cylinder)
obj.Placement.Base=FreeCAD.Vector(-0.73,0.39,0)
obj=doc.copyObject(cylinder)
obj.Placement.Base=FreeCAD.Vector(0.32,-0.21,0)
obj=doc.copyObject(cylinder)
obj.Placement.Base=FreeCAD.Vector(0.43,0.28,0)
obj=doc.copyObject(cylinder)
obj.Placement.Base=FreeCAD.Vector(-0.12,0.19,0)
obj=doc.copyObject(cylinder)
obj.Placement.Base=FreeCAD.Vector(0.26,0.62,0)
obj=doc.copyObject(cylinder)
obj.Placement.Base=FreeCAD.Vector(0.02,-0.25,0)
obj=doc.copyObject(cylinder)
obj.Placement.Base=FreeCAD.Vector(0.72,0.29,0)
obj=doc.copyObject(cylinder)
obj.Placement.Base=FreeCAD.Vector(0.52,0.62,0)
obj=doc.copyObject(cylinder)
obj.Placement.Base=FreeCAD.Vector(-0.67,0.65,0)
obj=doc.copyObject(cylinder)
obj.Placement.Base=FreeCAD.Vector(0.6,-0.08,0)
obj=doc.copyObject(cylinder)
obj.Placement.Base=FreeCAD.Vector(-0.27,-0.11,0)
obj=doc.copyObject(cylinder)
obj.Placement.Base=FreeCAD.Vector(0.15,0.06,0)
